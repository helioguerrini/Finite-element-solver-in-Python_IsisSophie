Attribute VB_Name = "ABRISCAE"
Sub iscae()
    IsisSophieCAE.show
End Sub

Attribute VB_Name = "ABRTR2D"
Sub t2d()
    TR2D.show
End Sub

Attribute VB_Name = "IsisSophieCAE"
Attribute VB_Base = "0{9B41B362-D87E-49CD-A253-7C4CCC9D8A08}{5B9998FF-1F1D-4F72-B098-9B589047C14D}"
Attribute VB_GlobalNameSpace = False
Attribute VB_Creatable = False
Attribute VB_PredeclaredId = True
Attribute VB_Exposed = False
Attribute VB_TemplateDerived = False
Attribute VB_Customizable = False
Private Sub Botao_Iniciar_Click()
Dim verfBlocoNOD_2D, verfBlocoF_NOD_2D, verfBlocoELEM_BAR_2D, verfBlocoAP_FIX_2D, verfBlocoAP_MV_2D As Boolean
Dim strNome_NOD_2D, strNome_F_NOD_2D, strNome_ELEM_BAR_2D, strNome_AP_FIX_2D, strNome_AP_MV_2D As String
Dim objBlocoINS As AcadBlock
Dim blrefINS As AcadBlockReference
Dim coorINS(0 To 2) As Double

verfBlocoNOD_2D = False
verfBlocoF_NOD_2D = False
verfBlocoELEM_BAR_2D = False
verfBlocoAP_FIX_2D = False
verfBlocoAP_MV_2D = False

coorINS(0) = 1E+18: coorINS(1) = 0: coorINS(2) = 0

For Each objBlocoINS In ThisDrawing.Blocks
    If objBlocoINS.Name = "NOD_2D" Then
        verfBlocoNOD_2D = True
    ElseIf objBlocoINS.Name = "F_NOD_2D" Then
        verfBlocoF_NOD_2D = True
    ElseIf objBlocoINS.Name = "ELEM_BAR_2D" Then
        verfBlocoELEM_BAR_2D = True
    ElseIf objBlocoINS.Name = "AP_FIX_2D" Then
        verfBlocoAP_FIX_2D = True
    ElseIf objBlocoINS.Name = "AP_MV_2D" Then
        verfBlocoAP_MV_2D = True
    End If
Next objBlocoINS

If verfBlocoNOD_2D = False Then
    nome_NOD_2D = "C:\Programas_VBA_CAD_helio\ISRAG_MEF\Blocos\Blocos_Trelica\NOD_2D.dwg"
    Set blrefINS = ThisDrawing.ModelSpace.InsertBlock(coorINS, nome_NOD_2D, 1, 1, 1, 0)
    blrefINS.Delete
End If

If verfBlocoF_NOD_2D = False Then
    nome_F_NOD_2D = "C:\Programas_VBA_CAD_helio\ISRAG_MEF\Blocos\Blocos_Trelica\F_NOD_2D.dwg"
    Set blrefINS = ThisDrawing.ModelSpace.InsertBlock(coorINS, nome_F_NOD_2D, 1, 1, 1, 0)
    blrefINS.Delete
End If

If verfBlocoELEM_BAR_2D = False Then
    nome_ELEM_BAR_2D = "C:\Programas_VBA_CAD_helio\ISRAG_MEF\Blocos\Blocos_Trelica\ELEM_BAR_2D.dwg"
    Set blrefINS = ThisDrawing.ModelSpace.InsertBlock(coorINS, nome_ELEM_BAR_2D, 1, 1, 1, 0)
    blrefINS.Delete
End If

If verfBlocoAP_FIX_2D = False Then
    nome_AP_FIX_2D = "C:\Programas_VBA_CAD_helio\ISRAG_MEF\Blocos\Blocos_Comuns\AP_FIX_2D.dwg"
    Set blrefINS = ThisDrawing.ModelSpace.InsertBlock(coorINS, nome_AP_FIX_2D, 1, 1, 1, 0)
    blrefINS.Delete
End If

If verfBlocoAP_MV_2D = False Then
    nome_AP_MV_2D = "C:\Programas_VBA_CAD_helio\ISRAG_MEF\Blocos\Blocos_Comuns\AP_MV_2D.dwg"
    Set blrefINS = ThisDrawing.ModelSpace.InsertBlock(coorINS, nome_AP_MV_2D, 1, 1, 1, 0)
    blrefINS.Delete
End If

'############################# ATIVA O SOLVER #########################
    Dim caminhoEXE As String
    Dim strG As String
   
    'caminhoEXE = "C:\executaveis_python\Isis Sophie CAE\dist\SolverTrelicaPlana.exe"
    'caminhoEXE = "D:\Projetos_Prog\ISRAG_RX1.exe"
    caminhoEXE = "C:\ISTemp\Solver\IS_SOLVER_EST_TP2D.exe"
    strG = "/G"

    'Call Shell("""" & caminhoEXE & """ """ & strG & """", vbNormalFocus)
    Call Shell(caminhoEXE, vbNormalFocus)

'#######################################################################

Unload IsisSophieCAE
TR2D.show


End Sub

Private Sub Image1_BeforeDragOver(ByVal Cancel As MSForms.ReturnBoolean, ByVal Data As MSForms.DataObject, ByVal X As Single, ByVal Y As Single, ByVal DragState As MSForms.fmDragState, ByVal Effect As MSForms.ReturnEffect, ByVal Shift As Integer)

End Sub

Private Sub UserForm_Click()

End Sub

Attribute VB_Name = "Module1"
Sub malhateste()
Dim selSet As AcadSelectionSet
Dim ponto1 As Variant, ponto2 As Variant

'ThisDrawing.SelectionSets.Item("MySelectionSet").Delete

On Error Resume Next
'**************************************************************************************
'Cria um novo AcadSelectionSet e adiciona todos os objetos selecionados pelo usuário
Set selSet = ThisDrawing.SelectionSets.Add("MySelectionSet")

With ThisDrawing.Utility
    .InitializeUserInput 1
    ponto1 = .GetPoint(, "Click no primeiro ponto")
    ponto2 = .GetCorner(ponto1, "Click no segundo ponto oposto")
    selSet.Select SelectionMode, ponto1, ponto2
    selSet.Highlight True
    selSet.Update
    .GetString False, "Pressione enter"
End With
'**************************************************************************************

'Define as variáveis necessárias
Dim objEnt01 As Object
Dim vecPtsKnow() As Double
Dim vecEspelho() As Double
ReDim vecPtsKnow(0 To 1, 0 To 1)

Dim nomeLinhaBarra As String
Dim ptsInicial, ptsFinal As Variant
Dim lineBarra As AcadLine
Dim contador As Integer
Dim decz As Boolean
Dim ktd, qtd As Boolean
Dim contktd, contqtd As Integer

decz = False
ktd = False
qtd = False
contador = 0
'Percorre todos os objetos selecionados selecionados
For Each objEnt01 In selSet
    'Condicional que separa apenas as linhas da coleção de objetos
    If TypeOf objEnt01 Is AcadLine Then
        Set lineBarra = objEnt01
            'Condicional que separa apenas as linhas da coleção de objetos com layers de nome Barra
            If lineBarra.Layer = "Barra" Then
            
                If decz = True Then
                    ptsInicial = lineBarra.StartPoint
                    ptsFinal = lineBarra.EndPoint
                    'MsgBox "Ponto inicial da linha corrente: " & str(ptsInicial(0)) & ":" & str(ptsInicial(1))
                    'MsgBox "Ponto final da linha corrente: " & str(ptsFinal(0)) & ":" & str(ptsFinal(1))
                    For i = 0 To UBound(vecPtsKnow)
                        'MsgBox str(vecPtsKnow(i, 0)) & ":" & str(vecPtsKnow(i, 1))
                        If vecPtsKnow(i, 0) = ptsInicial(0) And vecPtsKnow(i, 1) = ptsInicial(1) Then
                            'MsgBox "O ponto inicial da linha corrente está contida no vetor: " & str(vecPtsKnow(i, 0)) & ":" & str(vecPtsKnow(i, 1))
                            ktd = True
                        End If
                        
                        If vecPtsKnow(i, 0) = ptsFinal(0) And vecPtsKnow(i, 1) = ptsFinal(1) Then
                            'MsgBox "O ponto final da linha corrente está contida no vetor: " & str(vecPtsKnow(i, 0)) & ":" & str(vecPtsKnow(i, 1))
                            qtd = True
                        End If
                    Next i
                        '#######
                    'Redimensiona o vetor de pontos conhecidos e adiciona o novo ponto inicial da linha corrente
                    If ktd = False Then
                        contador = UBound(vecPtsKnow)
                        ReDim vecEspelho(0 To contador, 0 To 1)
                        'Transfere os dados do vetor de pontos conhecidos para o vetor espelho
                        For i = 0 To UBound(vecPtsKnow)
                            vecEspelho(i, 0) = vecPtsKnow(i, 0)
                            vecEspelho(i, 1) = vecPtsKnow(i, 1)
                            'MsgBox str(vecEspelho(i, 0)) & ":" & str(vecEspelho(i, 1))
                        Next i
                        'Redimensiona o vetor de pontos
                        contador = UBound(vecPtsKnow) + 1
                        ReDim vecPtsKnow(0 To contador, 0 To 1)
                        'Transfere os dados do vetor espelho para o vetor de pontos conhecidos
                        For i = 0 To UBound(vecEspelho)
                            vecPtsKnow(i, 0) = vecEspelho(i, 0)
                            vecPtsKnow(i, 1) = vecEspelho(i, 1)
                        Next i
                        'Adiciona o novo ponto ao vetor de pontos conhecidos
                        vecPtsKnow(contador, 0) = ptsInicial(0)
                        vecPtsKnow(contador, 1) = ptsInicial(1)
                    End If

                    'Redimensiona o vetor de pontos conhecidos e adiciona o novo ponto final da linha corrente
                    If qtd = False Then
                        contador = UBound(vecPtsKnow)
                        ReDim vecEspelho(0 To contador, 0 To 1)
                        'Transfere os dados do vetor de pontos conhecidos para o vetor espelho
                        For i = 0 To UBound(vecPtsKnow)
                            For j = 0 To 1
                                vecEspelho(i, j) = vecPtsKnow(i, j)
                            Next j
                        Next i
                        'Redimensiona o vetor de pontos
                        contador = UBound(vecPtsKnow) + 1
                        ReDim vecPtsKnow(0 To contador, 0 To 1)
                        'Transfere os dados do vetor espelho para o vetor de pontos conhecidos
                        For i = 0 To UBound(vecEspelho)
                            For j = 0 To 1
                                vecPtsKnow(i, j) = vecEspelho(i, j)
                            Next j
                        Next i
                        'Adiciona o novo ponto ao vetor de pontos conhecidos
                        vecPtsKnow(contador, 0) = ptsFinal(0)
                        vecPtsKnow(contador, 1) = ptsFinal(1)
                    End If
                        'Reinicia as variáveis de decisão
                        ktd = False
                        qtd = False
                    
                End If
 
                If decz = False Then
                    'Obten as coordenadas das linhas
                    ptsInicial = lineBarra.StartPoint
                    ptsFinal = lineBarra.EndPoint
                    
                    vecPtsKnow(0, 0) = ptsInicial(0)
                    vecPtsKnow(0, 1) = ptsInicial(1)
                    vecPtsKnow(1, 0) = ptsFinal(0)
                    vecPtsKnow(1, 1) = ptsFinal(1)
                End If
            
                'Ativa a variável de decisão
                decz = True
            End If
    End If
    
Next objEnt01

For i = LBound(vecPtsKnow) To UBound(vecPtsKnow)
    MsgBox str(vecPtsKnow(i, 0)) & ":" & str(vecPtsKnow(i, 1))
Next i

selSet.Highlight False
selSet.Update
'Remove o AcadSelectionSet criado
ThisDrawing.SelectionSets.Item("MySelectionSet").Delete
ThisDrawing.Regen acAllViewports

End Sub

Attribute VB_Name = "Module2"
Sub malhaveri()

Dim selSet As AcadSelectionSet
Dim ponto1 As Variant, ponto2 As Variant

'ThisDrawing.SelectionSets.Item("MySelectionSet").Delete

On Error Resume Next
'**************************************************************************************
'Cria um novo AcadSelectionSet e adiciona todos os objetos selecionados pelo usuário
Set selSet = ThisDrawing.SelectionSets.Add("MySelectionSet")

With ThisDrawing.Utility
    .InitializeUserInput 1
    ponto1 = .GetPoint(, "Click no primeiro ponto")
    ponto2 = .GetCorner(ponto1, "Click no segundo ponto oposto")
    selSet.Select SelectionMode, ponto1, ponto2
    selSet.Highlight True
    selSet.Update
    .GetString False, "Pressione enter"
End With
'**************************************************************************************

'Define as variáveis necessárias
Dim objEnt01 As Object
Dim vecPtsKnow() As Double
Dim vecEspelho() As Double
ReDim vecPtsKnow(0 To 1, 0 To 1)

Dim nomeLinhaBarra As String
Dim ptsInicial, ptsFinal As Variant
Dim lineBarra As AcadLine
Dim contador As Integer
Dim decz As Boolean
Dim ktd, qtd As Boolean
Dim contktd, contqtd As Integer

decz = False
ktd = False
qtd = False
contador = 0
'Percorre todos os objetos selecionados selecionados
For Each objEnt01 In selSet
    'Condicional que separa apenas as linhas da coleção de objetos
    If TypeOf objEnt01 Is AcadLine Then
        Set lineBarra = objEnt01
            'Condicional que separa apenas as linhas da coleção de objetos com layers de nome Barra
            If lineBarra.Layer = "Barra" Then
            
                If decz = True Then
                    ptsInicial = lineBarra.StartPoint
                    ptsFinal = lineBarra.EndPoint
                    'MsgBox "Ponto inicial da linha corrente: " & str(ptsInicial(0)) & ":" & str(ptsInicial(1))
                    'MsgBox "Ponto final da linha corrente: " & str(ptsFinal(0)) & ":" & str(ptsFinal(1))
                    For i = 0 To UBound(vecPtsKnow)
                        'MsgBox str(vecPtsKnow(i, 0)) & ":" & str(vecPtsKnow(i, 1))
                        If vecPtsKnow(i, 0) = ptsInicial(0) And vecPtsKnow(i, 1) = ptsInicial(1) Then
                            'MsgBox "O ponto inicial da linha corrente está contida no vetor: " & str(vecPtsKnow(i, 0)) & ":" & str(vecPtsKnow(i, 1))
                            ktd = True
                        End If
                        
                        If vecPtsKnow(i, 0) = ptsFinal(0) And vecPtsKnow(i, 1) = ptsFinal(1) Then
                            'MsgBox "O ponto final da linha corrente está contida no vetor: " & str(vecPtsKnow(i, 0)) & ":" & str(vecPtsKnow(i, 1))
                            qtd = True
                        End If
                    Next i
                        '#######
                    'Redimensiona o vetor de pontos conhecidos e adiciona o novo ponto inicial da linha corrente
                    If ktd = False Then
                        contador = UBound(vecPtsKnow)
                        ReDim vecEspelho(0 To contador, 0 To 1)
                        'Transfere os dados do vetor de pontos conhecidos para o vetor espelho
                        For i = 0 To UBound(vecPtsKnow)
                            vecEspelho(i, 0) = vecPtsKnow(i, 0)
                            vecEspelho(i, 1) = vecPtsKnow(i, 1)
                            'MsgBox str(vecEspelho(i, 0)) & ":" & str(vecEspelho(i, 1))
                        Next i
                        'Redimensiona o vetor de pontos
                        contador = UBound(vecPtsKnow) + 1
                        ReDim vecPtsKnow(0 To contador, 0 To 1)
                        'Transfere os dados do vetor espelho para o vetor de pontos conhecidos
                        For i = 0 To UBound(vecEspelho)
                            vecPtsKnow(i, 0) = vecEspelho(i, 0)
                            vecPtsKnow(i, 1) = vecEspelho(i, 1)
                        Next i
                        'Adiciona o novo ponto ao vetor de pontos conhecidos
                        vecPtsKnow(contador, 0) = ptsInicial(0)
                        vecPtsKnow(contador, 1) = ptsInicial(1)
                    End If

                    'Redimensiona o vetor de pontos conhecidos e adiciona o novo ponto final da linha corrente
                    If qtd = False Then
                        contador = UBound(vecPtsKnow)
                        ReDim vecEspelho(0 To contador, 0 To 1)
                        'Transfere os dados do vetor de pontos conhecidos para o vetor espelho
                        For i = 0 To UBound(vecPtsKnow)
                            For j = 0 To 1
                                vecEspelho(i, j) = vecPtsKnow(i, j)
                            Next j
                        Next i
                        'Redimensiona o vetor de pontos
                        contador = UBound(vecPtsKnow) + 1
                        ReDim vecPtsKnow(0 To contador, 0 To 1)
                        'Transfere os dados do vetor espelho para o vetor de pontos conhecidos
                        For i = 0 To UBound(vecEspelho)
                            For j = 0 To 1
                                vecPtsKnow(i, j) = vecEspelho(i, j)
                            Next j
                        Next i
                        'Adiciona o novo ponto ao vetor de pontos conhecidos
                        vecPtsKnow(contador, 0) = ptsFinal(0)
                        vecPtsKnow(contador, 1) = ptsFinal(1)
                    End If
                        'Reinicia as variáveis de decisão
                        ktd = False
                        qtd = False
                    
                End If
 
                If decz = False Then
                    'Obten as coordenadas das linhas
                    ptsInicial = lineBarra.StartPoint
                    ptsFinal = lineBarra.EndPoint
                    
                    vecPtsKnow(0, 0) = ptsInicial(0)
                    vecPtsKnow(0, 1) = ptsInicial(1)
                    vecPtsKnow(1, 0) = ptsFinal(0)
                    vecPtsKnow(1, 1) = ptsFinal(1)
                End If
            
                'Ativa a variável de decisão
                decz = True
            End If
    End If
    
Next objEnt01

'For i = LBound(vecPtsKnow) To UBound(vecPtsKnow)
    'MsgBox str(vecPtsKnow(i, 0)) & ":" & str(vecPtsKnow(i, 1))
'Next i

Dim coor(0 To 2) As Double
Dim bl01 As AcadBlockReference
Dim Escala As Integer
Dim AtrValor As Variant

Escala = ThisDrawing.GetVariable("useri1")
strNomeBloco = "NOD_2D"

'Inseri os nós numerando-os
For i = 0 To UBound(vecPtsKnow)
    coor(0) = vecPtsKnow(i, 0)
    coor(1) = vecPtsKnow(i, 1)
    Set bl01 = ThisDrawing.ModelSpace.InsertBlock(coor, strNomeBloco, Escala, Escala, Escala, 0)
    
    For Each AtrValor In bl01.GetAttributes
        AtrValor.TextString = i + 1
    Next AtrValor

Next i

'#################################################################################################################################
Dim medPt(0 To 2) As Double
strNomeBloco = "ELEM_BAR_2D"
contador = 1
'Percorre todos os objetos selecionados selecionados
For Each objEnt01 In selSet
    'Condicional que separa apenas as linhas da coleção de objetos
    If TypeOf objEnt01 Is AcadLine Then
        Set lineBarra = objEnt01
            'Condicional que separa apenas as linhas da coleção de objetos com layers de nome Barra
            If lineBarra.Layer = "Barra" Then
                'Obtém as coordenadas iniciais e finais do segmento de reta
                ptsInicial = lineBarra.StartPoint
                ptsFinal = lineBarra.EndPoint
                
                'Calcula-se o ponto médio
                medPt(0) = 0.5 * (ptsInicial(0) + ptsFinal(0))
                medPt(1) = 0.5 * (ptsInicial(1) + ptsFinal(1))
                medPt(2) = 0.5 * (ptsInicial(2) + ptsFinal(2))
                
                'Insere o bloco do elemento no ponto médio do segmento de reta
                Set bl01 = ThisDrawing.ModelSpace.InsertBlock(medPt, strNomeBloco, Escala, Escala, Escala, 0)
                
                'Numera o elemento na sequencia das linhas "Barras" selecionadas no desenho
                For Each AtrValor In bl01.GetAttributes
                    If AtrValor.TagString = "BAR_2D" Then
                        AtrValor.TextString = contador
                    End If
                Next AtrValor
                contador = contador + 1
      
                'Laço que varre todas as coordenadas nodais (todos os pontos conhecidos)
                For i = 0 To UBound(vecPtsKnow)
                    If vecPtsKnow(i, 0) = ptsInicial(0) And vecPtsKnow(i, 1) = ptsInicial(1) Then
                        'Numera o nó inicial no atributo "NOD_I_2D" do elemento
                        'que corresponde a linha (barra) corrente
                        For Each AtrValor In bl01.GetAttributes
                            If AtrValor.TagString = "NOD_I_2D" Then
                                AtrValor.TextString = str(i + 1)
                            End If
                        Next AtrValor
                    End If
                    
                    If vecPtsKnow(i, 0) = ptsFinal(0) And vecPtsKnow(i, 1) = ptsFinal(1) Then
                        'Numera o nó final no atributo "NOD_F_2D" do elemento
                        'que corresponde a linha (barra) corrente
                        For Each AtrValor In bl01.GetAttributes
                            If AtrValor.TagString = "NOD_F_2D" Then
                                AtrValor.TextString = str(i + 1)
                            End If
                        Next AtrValor
                    End If
                
                Next i
            
            End If
    End If
    

Next objEnt01

'#################################################################################################################################

selSet.Highlight False
selSet.Update
'Remove o AcadSelectionSet criado
ThisDrawing.SelectionSets.Item("MySelectionSet").Delete
ThisDrawing.Regen acAllViewports

End Sub

Attribute VB_Name = "TR2D"
Attribute VB_Base = "0{B413D5DD-9618-4C3D-8DBC-016812288F63}{53C1ECF5-7852-4669-93A2-5E73AF50A3C1}"
Attribute VB_GlobalNameSpace = False
Attribute VB_Creatable = False
Attribute VB_PredeclaredId = True
Attribute VB_Exposed = False
Attribute VB_TemplateDerived = False
Attribute VB_Customizable = False
Public FecharTR2D As Boolean

Private Sub AplicProp_Click()

End Sub

Private Sub BTPROP_Click()
frm_propriedades.show
End Sub

Private Sub Analise01_Click()
    ' Título da janela do programa .exe
    Dim tituloJanela As String
    Dim T1 As Double
    Dim T2 As Double
    
    On Error Resume Next
    SendKeys "{ESC}"
    
    'tituloJanela = "ISRAG_RX1.exe"
    tituloJanela = "IS_SOLVER_EST_TP2D.exe"
    
    ' Comando a ser enviado para o programa .exe
    Dim comando As String
    comando = "@#$Executar_analise$#@"
    
    ' Ativar a janela do programa .exe
    AppActivate tituloJanela
    
    TR2D.Hide
    
    ' Aguardar um pequeno intervalo para garantir que a janela seja ativada
    T1 = VBA.Timer
    T2 = 0
    While T2 - T1 < 3#
        T2 = VBA.Timer
    Wend
    
    ' Enviar o comando para a janela do programa .exe
    'SendKeys comando & "{ENTER}", True
    Set WshShell = CreateObject("WScript.Shell")
    WshShell.SendKeys comando & "{ENTER}", True
    
    Call SendKeys("{NUMLOCK}", True)
End Sub

Private Sub ApgApoio_Click()

Dim selSet As AcadSelectionSet
Dim ponto1 As Variant, ponto2 As Variant
Dim VetNmBloc() As Variant
Dim contador As Integer

'ThisDrawing.SelectionSets.Item("MySelectionSet").Delete
TR2D.Hide
On Error Resume Next
'**************************************************************************************
'Cria um novo AcadSelectionSet e adiciona todos os objetos selecionados pelo usuário
Set selSet = ThisDrawing.SelectionSets.Add("MySelectionSet")
On Error GoTo Erro
With ThisDrawing.Utility
    .InitializeUserInput 1
    ponto1 = .GetPoint(, "Click no primeiro ponto")
    ponto2 = .GetCorner(ponto1, "Click no segundo ponto oposto")
    selSet.Select SelectionMode, ponto1, ponto2
    selSet.Highlight True
    selSet.Update
    .GetString False, "Pressione enter"
End With
'**************************************************************************************

'Percorre todos os blocos selecionados
contador = 1
For Each objEnt01 In selSet
    If StrComp(objEnt01.EntityName, "AcDbBlockReference", 1) = 0 Then
        nomeBloco = objEnt01.Name
        'Verifica se o nome do bloco é "ELEM_BAR_2D"
        If nomeBloco = "AP_FIX_2D" Then
            Set blk = objEnt01
            blk.Delete
        ElseIf nomeBloco = "AP_MV_2D" Then
            Set blk = objEnt01
            blk.Delete
        End If
    End If
Next objEnt01

'''''''''''''''''''''''''''''''''''''''''''''''''''''''''''''''''''''''''''''''''''''''''

'Remove o AcadSelectionSet criado
ThisDrawing.SelectionSets.Item("MySelectionSet").Delete
ThisDrawing.Regen acAllViewports
TR2D.show
On Error GoTo 0
Exit Sub

Erro:
    'Remove o AcadSelectionSet criado
    ThisDrawing.SelectionSets.Item("MySelectionSet").Delete
    ThisDrawing.Regen acAllViewports
    TR2D.show
    On Error GoTo 0
End Sub

Private Sub ApgBarras_Click()
Dim selSet As AcadSelectionSet
Dim ponto1 As Variant, ponto2 As Variant
Dim VetNmBloc() As Variant
Dim contador As Integer

'ThisDrawing.SelectionSets.Item("MySelectionSet").Delete
TR2D.Hide
On Error Resume Next
'**************************************************************************************
'Cria um novo AcadSelectionSet e adiciona todos os objetos selecionados pelo usuário
Set selSet = ThisDrawing.SelectionSets.Add("MySelectionSet")
On Error GoTo Erro
With ThisDrawing.Utility
    .InitializeUserInput 1
    ponto1 = .GetPoint(, "Click no primeiro ponto")
    ponto2 = .GetCorner(ponto1, "Click no segundo ponto oposto")
    selSet.Select SelectionMode, ponto1, ponto2
    selSet.Highlight True
    selSet.Update
    .GetString False, "Pressione enter"
End With

'**************************************************************************************

'Percorre todos os blocos selecionados
contador = 1
For Each objEnt01 In selSet
    If StrComp(objEnt01.EntityName, "AcDbBlockReference", 1) = 0 Then
        nomeBloco = objEnt01.Name
        'Verifica se o nome do bloco é "ELEM_BAR_2D"
        If nomeBloco = "ELEM_BAR_2D" Then
            Set blk = objEnt01
            blk.Delete
        End If
    End If
Next objEnt01

'''''''''''''''''''''''''''''''''''''''''''''''''''''''''''''''''''''''''''''''''''''''''

'Remove o AcadSelectionSet criado
ThisDrawing.SelectionSets.Item("MySelectionSet").Delete
ThisDrawing.Regen acAllViewports
TR2D.show
On Error GoTo 0
Exit Sub
Erro:
    'Remove o AcadSelectionSet criado
    ThisDrawing.SelectionSets.Item("MySelectionSet").Delete
    ThisDrawing.Regen acAllViewports
    TR2D.show
    On Error GoTo 0
End Sub

Private Sub ApgNos_Click()
Dim selSet As AcadSelectionSet
Dim ponto1 As Variant, ponto2 As Variant
Dim VetNmBloc() As Variant
Dim contador As Integer

'ThisDrawing.SelectionSets.Item("MySelectionSet").Delete
TR2D.Hide
On Error Resume Next
'**************************************************************************************
'Cria um novo AcadSelectionSet e adiciona todos os objetos selecionados pelo usuário
Set selSet = ThisDrawing.SelectionSets.Add("MySelectionSet")
On Error GoTo Erro
With ThisDrawing.Utility
    .InitializeUserInput 1
    ponto1 = .GetPoint(, "Click no primeiro ponto")
    ponto2 = .GetCorner(ponto1, "Click no segundo ponto oposto")
    selSet.Select SelectionMode, ponto1, ponto2
    selSet.Highlight True
    selSet.Update
    .GetString False, "Pressione enter"
End With

'**************************************************************************************

'Percorre todos os blocos selecionados
contador = 1
For Each objEnt01 In selSet
    If StrComp(objEnt01.EntityName, "AcDbBlockReference", 1) = 0 Then
        nomeBloco = objEnt01.Name
        'Verifica se o nome do bloco é "NOD_2D"
        If nomeBloco = "NOD_2D" Then
            Set blk = objEnt01
            blk.Delete
        End If
    End If
Next objEnt01

'''''''''''''''''''''''''''''''''''''''''''''''''''''''''''''''''''''''''''''''''''''''''

'Remove o AcadSelectionSet criado
ThisDrawing.SelectionSets.Item("MySelectionSet").Delete
ThisDrawing.Regen acAllViewports
TR2D.show
On Error GoTo 0
Exit Sub
Erro:
    'Remove o AcadSelectionSet criado
    ThisDrawing.SelectionSets.Item("MySelectionSet").Delete
    ThisDrawing.Regen acAllViewports
    TR2D.show
    On Error GoTo 0
End Sub

Private Sub ArrayND_Click()
Dim modp, modq, Nx, Ny, sel As Double
Dim bl01 As AcadBlockReference
Dim att(0 To 2) As AcadAttributeReference
Dim var As Variant
Dim Dx, Dy As Double
Dim a(0 To 2) As Double
Dim b(0 To 2) As Double
Dim c(0 To 2) As Double
Dim p(0 To 2) As Double
Dim q(0 To 2) As Double
Dim e1(0 To 2) As Double
Dim e2(0 To 2) As Double
Dim r1(0 To 2) As Double
Dim r2(0 To 2) As Double
Dim R(0 To 2) As Double
Dim coor(0 To 2) As Double
Dim strNomeBloco As String
Dim Escala As Integer
Dim angu As Variant
Dim objBloco As AcadBlock


Escala = ThisDrawing.GetVariable("useri1")
ThisDrawing.SetVariable "useri1", Escala
strNomeBloco = "NOD_2D"

TR2D.Hide

If Escala = 0 Then
    MsgBox "Escala não definida ", vbApplicationModal + vbCritical, "Aviso"
Else



ThisDrawing.Utility.Prompt "Click em três vértices de um paralelogramo:   "
'On Error GoTo Erro
    pto1 = ThisDrawing.Utility.GetPoint(, "Click no primeiro ponto:")
    pto2 = ThisDrawing.Utility.GetPoint(, "Click no segundo ponto:")
    pto3 = ThisDrawing.Utility.GetPoint(, "Click no terceiro ponto:")
    
    a(0) = pto1(0)
    a(1) = pto1(1)
    b(0) = pto2(0)
    b(1) = pto2(1)
    c(0) = pto3(0)
    c(1) = pto3(1)
    
    Nx = Val(TextBox3.Text): Ny = Val(TextBox4.Text)
    
    p(0) = b(0) - a(0): p(1) = b(1) - a(1)
    q(0) = c(0) - b(0): q(1) = c(1) - b(1)
    
    modp = ((p(0)) ^ 2 + (p(1)) ^ 2) ^ 0.5
    modq = ((q(0)) ^ 2 + (q(1)) ^ 2) ^ 0.5
    
    If modq = 0 Then
        e2(0) = 0
        e2(1) = 0
    Else
        e1(0) = p(0) / modp: e1(1) = p(1) / modp
        e2(0) = q(0) / modq: e2(1) = q(1) / modq
    End If
    Dx = modp / (Nx - 1): Dy = modq / (Ny - 1)
    
    If e2(0) = 0 Then
        e2(0) = 1E-30
    End If
    
    For i = 1 To Ny
        For j = 1 To Nx
            'r1(0) = (Dx * e1(0) / 2) + (j - 1) * (Dx * e1(0)): r1(1) = (Dx * e1(1) / 2) + (j - 1) * (Dx * e1(1))
            'r2(0) = (Dy * e2(0) / 2) + (i - 1) * (Dy * e2(0)): r2(1) = (Dy * e2(1) / 2) + (i - 1) * (Dy * e2(1))
            
            r1(0) = (j - 1) * (Dx * e1(0)): r1(1) = (j - 1) * (Dx * e1(1))
            r2(0) = (i - 1) * (Dy * e2(0)): r2(1) = (i - 1) * (Dy * e2(1))
            
            
            R(0) = r1(0) + r2(0): R(1) = r1(1) + r2(1)
            
            coor(0) = a(0) + R(0)
            coor(1) = a(1) + R(1)
            
            If sel = 1 Then
                angu = Atn(e2(1) / e2(0))
            ElseIf sel = 2 Then
                angu = Atn(e2(1) / e2(0)) + 1.5707963267949
            Else
            End If
            If angu > 1.5707963267949 Then
                angu = angu - 3.1415926536
            Else
            End If
                        
            Set bl01 = ThisDrawing.ModelSpace.InsertBlock(coor, strNomeBloco, Escala, Escala, Escala, angu)
            var = bl01.GetAttributes
            Set att(0) = var(0)
            att(0).Rotation = 0
        Next j
    Next i

'Erro:
    'MsgBox "Erro devido ao cancelamento da rotina, parâmetros não indicados corretamente ou blocos não carregados no desenho", vbApplicationModal + vbCritical, "Erro"
End If
ThisDrawing.Regen acAllViewports
TR2D.show

End Sub

Private Sub CheckBox1_Change()
ComboBox2.Enabled = CheckBox1.Value
TextBox1.Locked = CheckBox1.Value
TextBox2.Locked = CheckBox1.Value
End Sub

Private Sub CheckBox1_Click()


End Sub

Private Sub ComboBox1_Change()

End Sub

Private Sub ComboBox2_Change()

End Sub

Private Sub CommandButton1_Click()

'Declaração de variáveis
Dim coor(0 To 2) As Double
Dim bl01 As AcadBlockReference
Dim Escala As Integer
Dim osn As Integer
Dim a As Integer
Dim objBloco As AcadBlock
Dim strNomeBloco As String
Dim var As Variant
Dim att(0 To 20) As AcadAttributeReference
Dim AtrValor As Variant
Dim pto As Variant
Dim verfBloco As Boolean
Dim contador As Integer

'Ocultar a caixa de dialogo
TR2D.Hide
'Inicia a variável de verificação da existencia do bloco do nó
verfBloco = False
'Inicia a variável contador
'If CLng(Me.Label4.Caption) > 0 Then
    'contador = CLng(Me.Label4.Caption) + 1
'Else
    contador = 1
'End If

Escala = ThisDrawing.GetVariable("useri1") 'Variável que recebe o valor decimal da escala
ThisDrawing.SetVariable "useri1", Escala

'Condicional que verifica se a escala não foi definida e, portanto, tem o valor nulo (zero)
If Escala = 0 Then
    MsgBox "Escala não definida ", vbApplicationModal + vbCritical, "Aviso"
Else
    'Verifica se o bloco existe no desenho
    strNomeBloco = "NOD_2D"
    For Each objBloco In ThisDrawing.Blocks
        If 0 = StrComp(objBloco.Name, strNomeBloco, vbTextCompare) Then
            verfBloco = True
        End If
    Next objBloco
    
    If verfBloco = False Then
        'Caixa de mensagem informando a falta do bloco no desenho
        MsgBox "O bloco '" & strNomeBloco & "' não existe em seu desenho.", vbApplicationModal + vbCritical, "Aviso"
    ElseIf verfBloco = True Then
        'Muda o osmode para a configuração 9
        osn = ThisDrawing.GetVariable("osmode")
        ThisDrawing.SetVariable "osmode", 9
        
        On Error GoTo Erro
        While contador < 100001
            'Captura as coordenadas do ponto de inserção do bloco
            pto = ThisDrawing.Utility.GetPoint(, "Clique no ponto ou digite a coordenada:")
            coor(0) = pto(0): coor(1) = pto(1)
            'Insere o bloco do nó
            Set bl01 = ThisDrawing.ModelSpace.InsertBlock(coor, strNomeBloco, Escala, Escala, Escala, 0)
            'For Each AtrValor In bl01.GetAttributes
                'AtrValor.TextString = contador
                'Me.Label4.Caption = contador
            'Next AtrValor
            contador = contador + 1
        Wend
    Else
    End If
End If

Erro:
If bl01 Is Nothing Then
    ThisDrawing.Utility.Prompt "Rotina finalizada"
    ThisDrawing.SetVariable "osmode", osn
Else
End If

'Retorna a cai8xa de diálogo
TR2D.show

End Sub
Private Sub ApgForca_Click()

Dim selSet As AcadSelectionSet
Dim ponto1 As Variant, ponto2 As Variant
Dim VetNmBloc() As Variant
Dim contador As Integer

'ThisDrawing.SelectionSets.Item("MySelectionSet").Delete
TR2D.Hide
On Error Resume Next
'**************************************************************************************
'Cria um novo AcadSelectionSet e adiciona todos os objetos selecionados pelo usuário
Set selSet = ThisDrawing.SelectionSets.Add("MySelectionSet")
On Error GoTo Erro
With ThisDrawing.Utility
    .InitializeUserInput 1
    ponto1 = .GetPoint(, "Click no primeiro ponto")
    ponto2 = .GetCorner(ponto1, "Click no segundo ponto oposto")
    selSet.Select SelectionMode, ponto1, ponto2
    selSet.Highlight True
    selSet.Update
    .GetString False, "Pressione enter"
End With
'**************************************************************************************

'Percorre todos os blocos selecionados
contador = 1
For Each objEnt01 In selSet
    If StrComp(objEnt01.EntityName, "AcDbBlockReference", 1) = 0 Then
        nomeBloco = objEnt01.Name
        'Verifica se o nome do bloco é "ELEM_BAR_2D"
        If nomeBloco = "F_NOD_2D" Then
            Set blk = objEnt01
            blk.Delete
        End If
    End If
Next objEnt01

'''''''''''''''''''''''''''''''''''''''''''''''''''''''''''''''''''''''''''''''''''''''''

'Remove o AcadSelectionSet criado
selSet.Highlight False
selSet.Update
ThisDrawing.SelectionSets.Item("MySelectionSet").Delete
ThisDrawing.Regen acAllViewports
TR2D.show
On Error GoTo 0
Exit Sub

Erro:
    'Remove o AcadSelectionSet criado
    selSet.Highlight False
    selSet.Update
    ThisDrawing.SelectionSets.Item("MySelectionSet").Delete
    ThisDrawing.Regen acAllViewports
    TR2D.show
    On Error GoTo 0
End Sub


Private Sub EdtBarras_Click()

End Sub

Private Sub CommandButton7_Click()

End Sub

Private Sub EdtNos_Click()
On Error Resume Next
'Define as variáveis necessárias
Dim objEnt01 As Object

Dim blk As AcadBlockReference
Dim att As Variant
Dim nomeBloco As String
Dim valorAtt As String
Dim contador As Integer

contador = 1

'Percorre todos os blocos no desenho
For Each objEnt01 In ThisDrawing.ModelSpace
    If StrComp(objEnt01.EntityName, "AcDbBlockReference", 1) = 0 Then
        nomeBloco = objEnt01.Name
        'Verifica se o nome do bloco é "NOD_2D"
        If nomeBloco = "NOD_2D" Then
            Set blk = objEnt01
            For Each att In blk.GetAttributes
                'Verifica se o atributo é do tipo "NOD_2D"
                If att.TagString = "NOD_2D" Then
                    'Obtém o valor do atributo e adiciona à listbox
                    valorAtt = att.TextString
                    If valorAtt <> str(contador) Then
                        att.TextString = contador
                    End If
                End If
            Next att
        Me.Label4.Caption = contador
        contador = contador + 1
        End If
    End If
If contador = 1 Then
    Me.Label4.Caption = contador
End If
Next objEnt01
ThisDrawing.Regen acAllViewports
Resume Next
End Sub

Private Sub Image4_BeforeDragOver(ByVal Cancel As MSForms.ReturnBoolean, ByVal Data As MSForms.DataObject, ByVal X As Single, ByVal Y As Single, ByVal DragState As MSForms.fmDragState, ByVal Effect As MSForms.ReturnEffect, ByVal Shift As Integer)

End Sub

Private Sub gerarmalha_Click()
Dim selSet As AcadSelectionSet
Dim ponto1 As Variant, ponto2 As Variant

'ThisDrawing.SelectionSets.Item("MySelectionSet").Delete

'Ocultar a caixa de dialogo
TR2D.Hide

On Error Resume Next
'**************************************************************************************
'Cria um novo AcadSelectionSet e adiciona todos os objetos selecionados pelo usuário
Set selSet = ThisDrawing.SelectionSets.Add("MySelectionSet")

With ThisDrawing.Utility
    .InitializeUserInput 1
    ponto1 = .GetPoint(, "Click no primeiro ponto")
    ponto2 = .GetCorner(ponto1, "Click no segundo ponto oposto")
    selSet.Select SelectionMode, ponto1, ponto2
    selSet.Highlight True
    selSet.Update
    .GetString False, "Pressione enter"
End With
'**************************************************************************************

'Define as variáveis necessárias
Dim objEnt01 As Object
Dim vecPtsKnow() As Double
Dim vecEspelho() As Double
ReDim vecPtsKnow(0 To 1, 0 To 1)

Dim nomeLinhaBarra As String
Dim ptsInicial, ptsFinal As Variant
Dim lineBarra As AcadLine
Dim contador As Integer
Dim decz As Boolean
Dim ktd, qtd As Boolean
Dim contktd, contqtd As Integer

decz = False
ktd = False
qtd = False
contador = 0
'Percorre todos os objetos selecionados selecionados
For Each objEnt01 In selSet
    'Condicional que separa apenas as linhas da coleção de objetos
    If TypeOf objEnt01 Is AcadLine Then
        Set lineBarra = objEnt01
            'Condicional que separa apenas as linhas da coleção de objetos com layers de nome Barra
            If lineBarra.Layer = "Barra" Then
            
                If decz = True Then
                    ptsInicial = lineBarra.StartPoint
                    ptsFinal = lineBarra.EndPoint
                    'MsgBox "Ponto inicial da linha corrente: " & str(ptsInicial(0)) & ":" & str(ptsInicial(1))
                    'MsgBox "Ponto final da linha corrente: " & str(ptsFinal(0)) & ":" & str(ptsFinal(1))
                    For i = 0 To UBound(vecPtsKnow)
                        'MsgBox str(vecPtsKnow(i, 0)) & ":" & str(vecPtsKnow(i, 1))
                        If vecPtsKnow(i, 0) = ptsInicial(0) And vecPtsKnow(i, 1) = ptsInicial(1) Then
                            'MsgBox "O ponto inicial da linha corrente está contida no vetor: " & str(vecPtsKnow(i, 0)) & ":" & str(vecPtsKnow(i, 1))
                            ktd = True
                        End If
                        
                        If vecPtsKnow(i, 0) = ptsFinal(0) And vecPtsKnow(i, 1) = ptsFinal(1) Then
                            'MsgBox "O ponto final da linha corrente está contida no vetor: " & str(vecPtsKnow(i, 0)) & ":" & str(vecPtsKnow(i, 1))
                            qtd = True
                        End If
                    Next i
                        '#######
                    'Redimensiona o vetor de pontos conhecidos e adiciona o novo ponto inicial da linha corrente
                    If ktd = False Then
                        contador = UBound(vecPtsKnow)
                        ReDim vecEspelho(0 To contador, 0 To 1)
                        'Transfere os dados do vetor de pontos conhecidos para o vetor espelho
                        For i = 0 To UBound(vecPtsKnow)
                            vecEspelho(i, 0) = vecPtsKnow(i, 0)
                            vecEspelho(i, 1) = vecPtsKnow(i, 1)
                            'MsgBox str(vecEspelho(i, 0)) & ":" & str(vecEspelho(i, 1))
                        Next i
                        'Redimensiona o vetor de pontos
                        contador = UBound(vecPtsKnow) + 1
                        ReDim vecPtsKnow(0 To contador, 0 To 1)
                        'Transfere os dados do vetor espelho para o vetor de pontos conhecidos
                        For i = 0 To UBound(vecEspelho)
                            vecPtsKnow(i, 0) = vecEspelho(i, 0)
                            vecPtsKnow(i, 1) = vecEspelho(i, 1)
                        Next i
                        'Adiciona o novo ponto ao vetor de pontos conhecidos
                        vecPtsKnow(contador, 0) = ptsInicial(0)
                        vecPtsKnow(contador, 1) = ptsInicial(1)
                    End If

                    'Redimensiona o vetor de pontos conhecidos e adiciona o novo ponto final da linha corrente
                    If qtd = False Then
                        contador = UBound(vecPtsKnow)
                        ReDim vecEspelho(0 To contador, 0 To 1)
                        'Transfere os dados do vetor de pontos conhecidos para o vetor espelho
                        For i = 0 To UBound(vecPtsKnow)
                            For j = 0 To 1
                                vecEspelho(i, j) = vecPtsKnow(i, j)
                            Next j
                        Next i
                        'Redimensiona o vetor de pontos
                        contador = UBound(vecPtsKnow) + 1
                        ReDim vecPtsKnow(0 To contador, 0 To 1)
                        'Transfere os dados do vetor espelho para o vetor de pontos conhecidos
                        For i = 0 To UBound(vecEspelho)
                            For j = 0 To 1
                                vecPtsKnow(i, j) = vecEspelho(i, j)
                            Next j
                        Next i
                        'Adiciona o novo ponto ao vetor de pontos conhecidos
                        vecPtsKnow(contador, 0) = ptsFinal(0)
                        vecPtsKnow(contador, 1) = ptsFinal(1)
                    End If
                        'Reinicia as variáveis de decisão
                        ktd = False
                        qtd = False
                    
                End If
 
                If decz = False Then
                    'Obten as coordenadas das linhas
                    ptsInicial = lineBarra.StartPoint
                    ptsFinal = lineBarra.EndPoint
                    
                    vecPtsKnow(0, 0) = ptsInicial(0)
                    vecPtsKnow(0, 1) = ptsInicial(1)
                    vecPtsKnow(1, 0) = ptsFinal(0)
                    vecPtsKnow(1, 1) = ptsFinal(1)
                End If
            
                'Ativa a variável de decisão
                decz = True
            End If
    End If
    
Next objEnt01

'For i = LBound(vecPtsKnow) To UBound(vecPtsKnow)
    'MsgBox str(vecPtsKnow(i, 0)) & ":" & str(vecPtsKnow(i, 1))
'Next i

Dim coor(0 To 2) As Double
Dim bl01 As AcadBlockReference
Dim Escala As Integer
Dim AtrValor As Variant

Escala = ThisDrawing.GetVariable("useri1")
strNomeBloco = "NOD_2D"

'Inseri os nós numerando-os
For i = 0 To UBound(vecPtsKnow)
    coor(0) = vecPtsKnow(i, 0)
    coor(1) = vecPtsKnow(i, 1)
    Set bl01 = ThisDrawing.ModelSpace.InsertBlock(coor, strNomeBloco, Escala, Escala, Escala, 0)
    
    For Each AtrValor In bl01.GetAttributes
        AtrValor.TextString = i + 1
    Next AtrValor

Next i

'#################################################################################################################################
Dim medPt(0 To 2) As Double
strNomeBloco = "ELEM_BAR_2D"
contador = 1
'Percorre todos os objetos selecionados selecionados
For Each objEnt01 In selSet
    'Condicional que separa apenas as linhas da coleção de objetos
    If TypeOf objEnt01 Is AcadLine Then
        Set lineBarra = objEnt01
            'Condicional que separa apenas as linhas da coleção de objetos com layers de nome Barra
            If lineBarra.Layer = "Barra" Then
                'Obtém as coordenadas iniciais e finais do segmento de reta
                ptsInicial = lineBarra.StartPoint
                ptsFinal = lineBarra.EndPoint
                
                'Calcula-se o ponto médio
                medPt(0) = 0.5 * (ptsInicial(0) + ptsFinal(0))
                medPt(1) = 0.5 * (ptsInicial(1) + ptsFinal(1))
                medPt(2) = 0.5 * (ptsInicial(2) + ptsFinal(2))
                
                'Insere o bloco do elemento no ponto médio do segmento de reta
                Set bl01 = ThisDrawing.ModelSpace.InsertBlock(medPt, strNomeBloco, Escala, Escala, Escala, 0)
                
                'Numera o elemento na sequencia das linhas "Barras" selecionadas no desenho
                For Each AtrValor In bl01.GetAttributes
                    If AtrValor.TagString = "BAR_2D" Then
                        AtrValor.TextString = contador
                    End If
                Next AtrValor
                contador = contador + 1
      
                'Laço que varre todas as coordenadas nodais (todos os pontos conhecidos)
                For i = 0 To UBound(vecPtsKnow)
                    If vecPtsKnow(i, 0) = ptsInicial(0) And vecPtsKnow(i, 1) = ptsInicial(1) Then
                        'Numera o nó inicial no atributo "NOD_I_2D" do elemento
                        'que corresponde a linha (barra) corrente
                        For Each AtrValor In bl01.GetAttributes
                            If AtrValor.TagString = "NOD_I_2D" Then
                                AtrValor.TextString = str(i + 1)
                            End If
                        Next AtrValor
                    End If
                    
                    If vecPtsKnow(i, 0) = ptsFinal(0) And vecPtsKnow(i, 1) = ptsFinal(1) Then
                        'Numera o nó final no atributo "NOD_F_2D" do elemento
                        'que corresponde a linha (barra) corrente
                        For Each AtrValor In bl01.GetAttributes
                            If AtrValor.TagString = "NOD_F_2D" Then
                                AtrValor.TextString = str(i + 1)
                            End If
                        Next AtrValor
                    End If
                
                Next i
            
            End If
    End If
    

Next objEnt01

'#################################################################################################################################

selSet.Highlight False
selSet.Update
'Remove o AcadSelectionSet criado
ThisDrawing.SelectionSets.Item("MySelectionSet").Delete
ThisDrawing.Regen acAllViewports
'Ocultar a caixa de dialogo
TR2D.show
End Sub

Private Sub Label3_Click()

End Sub

Private Sub MULTF_Click()
Dim selSet As AcadSelectionSet
Dim ponto1 As Variant, ponto2 As Variant

'ThisDrawing.SelectionSets.Item("MySelectionSet").Delete

TR2D.Hide
On Error Resume Next
'**************************************************************************************
'Cria um novo AcadSelectionSet e adiciona todos os objetos selecionados pelo usuário
Set selSet = ThisDrawing.SelectionSets.Add("MySelectionSet")
On Error GoTo Erro
With ThisDrawing.Utility
    .InitializeUserInput 1
    ponto1 = .GetPoint(, "Click no primeiro ponto")
    ponto2 = .GetCorner(ponto1, "Click no segundo ponto oposto")
    selSet.Select SelectionMode, ponto1, ponto2
    selSet.Highlight True
    selSet.Update
    .GetString False, "Pressione enter"
End With
'**************************************************************************************

'Define as variáveis necessárias
Dim objEnt01 As Object
Dim blk As AcadBlockReference
Dim bl01 As AcadBlockReference
Dim att(0 To 20) As AcadAttributeReference
Dim nomeBloco As String
Dim coor(0 To 2) As Double
Dim insPontos As Variant
Dim Escala As Integer
Dim angu As Double
Dim vlrF As Variant
Dim var As Variant
Dim nomeNo As String
Dim AtrValor As Variant

'Variável que recebe o valor da intensidade da força
vlrF = ThisDrawing.Utility.GetString(1, vbCrLf & "Digite o valor da força: ")

'Variável que recebe o valor decimal da escala
Escala = ThisDrawing.GetVariable("useri1")

'Variável que recebe o valor do angulo da força
angu = ThisDrawing.Utility.GetAngle(coor, "Digite o ângulo da força:")

'Percorre todos os blocos selecionados
For Each objEnt01 In selSet
    If StrComp(objEnt01.EntityName, "AcDbBlockReference", 1) = 0 Then
        nomeBloco = objEnt01.Name
        'Verifica se o nome do bloco é "NOD_2D"
        If nomeBloco = "NOD_2D" Then
            Set blk = objEnt01
            insPontos = blk.InsertionPoint
            coor(0) = insPontos(0): coor(1) = insPontos(1): coor(2) = insPontos(2)
            Set bl01 = ThisDrawing.ModelSpace.InsertBlock(coor, "F_NOD_2D", Escala, Escala, Escala, 0)
            bl01.Rotate coor, angu
            
            'Acessa os atributos do objeto bloco (bl01) associando a variável matriz (var)
            var = bl01.GetAttributes
            ' Define a variável (att) aos elemento da matriz (var)
            Set att(0) = var(0)
            'Rotaciona o atributo para zero
            att(0).Rotation = 0
            
            'Coleta o número do nó
            For Each AtrValor In blk.GetAttributes
                nomeNo = AtrValor.TextString
            Next AtrValor
            
            'Registra a intensidade da força e o número do nó sujeito a força
            For Each var In bl01.GetAttributes
                If var.TagString = "F_2D" Then
                    var.TextString = vlrF
                Else
                    var.TextString = nomeNo
                End If
            Next var
    
        End If

    End If
    
Next objEnt01

'''''''''''''''''''''''''''''''''''''''''''''''''''''''''''''''''''''''''''''''''''''''''
selSet.Highlight False
selSet.Update
'Remove o AcadSelectionSet criado
ThisDrawing.SelectionSets.Item("MySelectionSet").Delete
ThisDrawing.Regen acAllViewports
On Error GoTo 0
TR2D.show
Exit Sub

Erro:
selSet.Highlight False
selSet.Update
'Remove o AcadSelectionSet criado
ThisDrawing.SelectionSets.Item("MySelectionSet").Delete
ThisDrawing.Regen acAllViewports
On Error GoTo 0
TR2D.show
End Sub

Private Sub OcultTR2D_Click()
    TR2D.Hide
End Sub

Private Sub TextBox1_KeyPress(ByVal KeyAscii As MSForms.ReturnInteger)
    Dim CaracterePermitido As Boolean
    CaracterePermitido = False 'Inicializa a variável como falsa
    
    'Verifica se o caractere digitado é numérico ou a letra "e"
    If IsNumeric(Chr(KeyAscii)) Or Chr(KeyAscii) = "e" Then
        CaracterePermitido = True 'Marca a variável como verdadeira
    End If
    
    'Cancela a tecla digitada se o caractere não for permitido
    If Not CaracterePermitido And KeyAscii <> 8 Then
        KeyAscii = 0
    End If
End Sub

Private Sub TextBox2_KeyPress(ByVal KeyAscii As MSForms.ReturnInteger)
    Dim CaracterePermitido As Boolean
    CaracterePermitido = False 'Inicializa a variável como falsa
    
    'Verifica se o caractere digitado é numérico ou a letra "e"
    If IsNumeric(Chr(KeyAscii)) Or Chr(KeyAscii) = "e" Then
        CaracterePermitido = True 'Marca a variável como verdadeira
    End If
    
    'Cancela a tecla digitada se o caractere não for permitido
    If Not CaracterePermitido And KeyAscii <> 8 Then
        KeyAscii = 0
    End If
End Sub

Private Sub TextBox3_Change()
    Dim CaracterePermitido As Boolean
    CaracterePermitido = False 'Inicializa a variável como falsa
    
    'Verifica se o caractere digitado é numérico ou a letra "e"
    If IsNumeric(Chr(KeyAscii)) Or Chr(KeyAscii) = "e" Then
        CaracterePermitido = True 'Marca a variável como verdadeira
    End If
    
    'Cancela a tecla digitada se o caractere não for permitido
    If Not CaracterePermitido And KeyAscii <> 8 Then
        KeyAscii = 0
    End If
End Sub

Private Sub TextBox4_Change()
    Dim CaracterePermitido As Boolean
    CaracterePermitido = False 'Inicializa a variável como falsa
    
    'Verifica se o caractere digitado é numérico ou a letra "e"
    If IsNumeric(Chr(KeyAscii)) Or Chr(KeyAscii) = "e" Then
        CaracterePermitido = True 'Marca a variável como verdadeira
    End If
    
    'Cancela a tecla digitada se o caractere não for permitido
    If Not CaracterePermitido And KeyAscii <> 8 Then
        KeyAscii = 0
    End If
End Sub

Private Sub TRBTVRF_Click()
'Define as variáveis necessárias
Dim objEnt01 As Object

Dim blk As AcadBlockReference
Dim att As Variant
Dim nomeBloco As String
Dim valorAtt1 As String
Dim valorAtt2 As String
Dim valorAtt3 As String
Dim X As Integer

'Limpa a listbox
ListBox1.Clear

'Percorre todos os blocos no desenho
For Each objEnt01 In ThisDrawing.ModelSpace
    If StrComp(objEnt01.EntityName, "AcDbBlockReference", 1) = 0 Then
        nomeBloco = objEnt01.Name
        'Verifica se o nome do bloco é "ELEM_BAR_2D"
        If nomeBloco = "ELEM_BAR_2D" Then
            Set blk = objEnt01
            For Each att In blk.GetAttributes
                'Verifica se o atributo é do tipo "BAR_2D"
                If att.TagString = "BAR_2D" Then
                    valorAtt1 = att.TextString
                    ListBox1.AddItem "Barra " & valorAtt1 & ":"
                ElseIf att.TagString = "MAT" Then
                    valorAtt2 = att.TextString
                    ListBox1.AddItem "  E = " & valorAtt2
                ElseIf att.TagString = "SEC" Then
                    valorAtt3 = att.TextString
                    ListBox1.AddItem "  A = " & valorAtt3
                End If
                
            Next att
        End If

    End If
    
Next objEnt01
End Sub

Private Sub CommandButton3_Click()

Dim intPoints01 As Variant
Dim intPoints02 As Variant
Dim linha As AcadLine
Dim objEnt01 As AcadEntity
Dim objEnt02 As AcadEntity
Dim objBRef01 As AcadBlockReference
Dim objBRef02 As AcadBlockReference
Dim startPt(0 To 2) As Double
Dim endPt(0 To 2) As Double
Dim medPt(0 To 2) As Double
Dim str As String
Dim varPick01 As Variant
Dim varPick02 As Variant
Dim contador As Integer
Dim blElem As AcadBlockReference
Dim Escala As Integer
Dim att, AtrValor As Variant
Dim nomeNo1, nomeNo2 As String
'Ocultar a caixa de dialogo
TR2D.Hide

Escala = ThisDrawing.GetVariable("useri1") 'Variável que recebe o valor decimal da escala
'Inicia a variável contador

'If CLng(Me.Label3.Caption) > 0 Then
'    contador = CLng(Me.Label3.Caption) + 1
'Else
'    contador = 1
'End If

contador = 1
'#########################################################################################
'Percorre todos os blocos no desenho
For Each objEnt01 In ThisDrawing.ModelSpace
    If StrComp(objEnt01.EntityName, "AcDbBlockReference", 1) = 0 Then
        nomeNo1 = objEnt01.Name
        'Verifica se o nome do bloco é "ELEM_BAR_2D"
        If nomeNo1 = "ELEM_BAR_2D" Then
            Set objBRef01 = objEnt01
            For Each att In objBRef01.GetAttributes
                'Verifica se o atributo é do tipo "BAR_2D"
                If att.TagString = "BAR_2D" Then
                    contador = CLng(att.TextString) + 1
                End If
            Next att
        End If
    End If
Next objEnt01
'#########################################################################################


On Error GoTo Erro
Do While contador < 1001
    With ThisDrawing.Utility
        .GetEntity objEnt01, varPick01, vbCr & "Selecione o primeiro nó: "
        Set objBRef01 = objEnt01
        
        'Coleta o número do primeiro nó
        For Each AtrValor In objBRef01.GetAttributes
            nomeNo1 = AtrValor.TextString
        Next AtrValor
                                    
        .GetEntity objEnt02, varPick02, vbCr & "Selecione o segundo nó: "
        Set objBRef02 = objEnt02

        'Coleta o número do segundo nó
        For Each AtrValor In objBRef02.GetAttributes
            nomeNo2 = AtrValor.TextString
        Next AtrValor

    End With
    ' Obtenção dos pontos de inserção
    intPoints01 = objBRef01.InsertionPoint
    intPoints02 = objBRef02.InsertionPoint
    
    startPt(0) = intPoints01(0): startPt(1) = intPoints01(1): startPt(2) = intPoints01(2)
    endPt(0) = intPoints02(0): endPt(1) = intPoints02(1): endPt(2) = intPoints02(2)
    
    'Verifica se os pontos são iguais. Se sim emite-se um aviso e abandona-se o laço
    If ((endPt(0) - startPt(0)) ^ 2 + (endPt(1) - startPt(1)) ^ 2) ^ 0.5 = 0 Then
        MsgBox "O nó possui ponto de inserção idêntico ao anterior. Por favor, selecione outro nó.", vbApplicationModal + vbCritical, "Aviso"
        Exit Do
    End If
    
    'Calcula-se o ponto médio
    medPt(0) = 0.5 * (intPoints01(0) + intPoints02(0)): medPt(1) = 0.5 * (intPoints01(1) + intPoints02(1)): medPt(2) = 0.5 * (intPoints01(2) + intPoints02(2))
        
    'Insere a linha que corresponde ao elemento de barra
    Set linha = ThisDrawing.ModelSpace.AddLine(startPt, endPt)
    
    
    'Insere o bloco com informações do elemento
    Set blElem = ThisDrawing.ModelSpace.InsertBlock(medPt, "ELEM_BAR_2D", Escala, Escala, Escala, 0)
    For Each AtrValor In blElem.GetAttributes
        'AtrValor.TextString = str(contador)
        If AtrValor.TagString = "BAR_2D" Then
            AtrValor.TextString = contador
            'Me.Label3.Caption = contador
        ElseIf AtrValor.TagString = "NOD_I_2D" Then
            AtrValor.TextString = nomeNo1
        ElseIf AtrValor.TagString = "NOD_F_2D" Then
            AtrValor.TextString = nomeNo2
        End If
    Next AtrValor
    
    ' Adiciona 1(um) ao contador
    contador = contador + 1
Loop
Erro:
'Retorna a caixa de diálogo
TR2D.show
End Sub

Private Sub CommandButton4_Click()

'Declaração de variáveis
Dim coor(0 To 2) As Double
Dim bl01 As AcadBlockReference
Dim Escala As Integer
Dim osn As Integer
Dim a As Integer
Dim objBloco As AcadBlock
Dim strNomeBloco As String
Dim var As Variant
Dim att(0 To 20) As AcadAttributeReference
Dim AtrValor As Variant
Dim vlrF As Variant
Dim verfBloco As Boolean
Dim contador As Integer
Dim angu As Double
Dim objBRef01 As AcadBlockReference
Dim intPoints01 As Variant
Dim objEnt01 As AcadEntity
Dim nomeNo As String

'Ocultar a caixa de dialogo
TR2D.Hide
'Inicia a variável de verificação da existencia do bloco do nó
verfBloco = False
'Inicia a variável contador
contador = 1

Escala = ThisDrawing.GetVariable("useri1") 'Variável que recebe o valor decimal da escala
ThisDrawing.SetVariable "useri1", Escala

'Condicional que verifica se a escala não foi definida e, portanto, tem o valor nulo (zero)
If Escala = 0 Then
    MsgBox "Escala não definida ", vbApplicationModal + vbCritical, "Aviso"
Else
    'Verifica se o bloco existe no desenho
    strNomeBloco = "F_NOD_2D"
    For Each objBloco In ThisDrawing.Blocks
        If 0 = StrComp(objBloco.Name, strNomeBloco, vbTextCompare) Then
            verfBloco = True
        End If
    Next objBloco
    
    If verfBloco = False Then
        'Caixa de mensagem informando a falta do bloco no desenho
        MsgBox "O bloco '" & strNomeBloco & "' não existe em seu desenho.", vbApplicationModal + vbCritical, "Aviso"
    ElseIf verfBloco = True Then
        
        On Error GoTo Erro
        Do While contador < 100001
            'Captura as coordenadas do ponto de inserção do bloco
            With ThisDrawing.Utility
                .GetEntity objEnt01, varPick01, vbCr & "Selecione o nó: "
                'Define o objeto como bloco
                Set objBRef01 = objEnt01
                'Verifica se o bloco é um nó pelo TAG do atributo NOD_2D
                For Each AtrValor In objBRef01.GetAttributes
                    If AtrValor.TagString <> "NOD_2D" Then
                        MsgBox "Esta entidade não é um nó", vbApplicationModal + vbCritical, "Aviso"
                        Exit Do
                    End If
                Next AtrValor
            End With
            'Obtém as coordenadas do nó (bloco nó) selecionado
            intPoints01 = objBRef01.InsertionPoint
            coor(0) = intPoints01(0): coor(1) = intPoints01(1): coor(2) = intPoints01(2)

            'Insere o bloco da força
            Set bl01 = ThisDrawing.ModelSpace.InsertBlock(coor, strNomeBloco, Escala, Escala, Escala, 0)
            angu = ThisDrawing.Utility.GetAngle(coor, "Indique a direção:")
            bl01.Rotate coor, angu
            
            'Acessa os atributos do objeto bloco (bl01) associando a variável matriz (var)
            var = bl01.GetAttributes
            ' Define a variável (att) aos elemento da matriz (var)
            Set att(0) = var(0)
            'Rotaciona o atributo para zero
            att(0).Rotation = 0
            
            'Coleta o número do nó
            For Each AtrValor In objBRef01.GetAttributes
                nomeNo = AtrValor.TextString
            Next AtrValor
            
            'Digita o valor da força
            vlrF = ThisDrawing.Utility.GetString(1, vbCrLf & "Digite o valor da força: ")
            
            'Registra a intensidade da força e o número do nó sujeito a força
            For Each var In bl01.GetAttributes
                If var.TagString = "F_2D" Then
                    var.TextString = vlrF
                Else
                    var.TextString = nomeNo
                End If
                
            Next var
            
            'Adiciona 1 ao contador
            contador = contador + 1
        Loop
    Else
    End If
End If

Erro:

'Retorna a caixa de diálogo
TR2D.show


End Sub

Private Sub CommandButton5_Click()


'Declaração de variáveis
Dim coor(0 To 2) As Double
Dim bl01 As AcadBlockReference
Dim Escala As Integer
Dim osn As Integer
Dim a As Integer
Dim objBloco As AcadBlock
Dim strNomeBloco As String
Dim var As Variant
Dim att(0 To 20) As AcadAttributeReference
Dim AtrValor As Variant
Dim pto As Variant
Dim verfBloco As Boolean
Dim contador As Integer
Dim angu As Double
Dim objEnt01 As AcadEntity

'Ocultar a caixa de dialogo
TR2D.Hide
'Inicia a variável de verificação da existencia do bloco do nó
verfBloco = False
'Inicia a variável contador
contador = 1

Escala = ThisDrawing.GetVariable("useri1") 'Variável que recebe o valor decimal da escala
ThisDrawing.SetVariable "useri1", Escala

'Condicional que verifica se a escala não foi definida e, portanto, tem o valor nulo (zero)
If Escala = 0 Then
    MsgBox "Escala não definida ", vbApplicationModal + vbCritical, "Aviso"
Else
    'Verifica se o bloco existe no desenho
    strNomeBloco = "AP_FIX_2D"
    For Each objBloco In ThisDrawing.Blocks
        If 0 = StrComp(objBloco.Name, strNomeBloco, vbTextCompare) Then
            verfBloco = True
        End If
    Next objBloco
    
    If verfBloco = False Then
        'Caixa de mensagem informando a falta do bloco no desenho
        MsgBox "O bloco '" & strNomeBloco & "' não existe em seu desenho.", vbApplicationModal + vbCritical, "Aviso"
    ElseIf verfBloco = True Then
        'Muda o osmode para a configuração 9
        osn = ThisDrawing.GetVariable("osmode")
        ThisDrawing.SetVariable "osmode", 9
        
        On Error GoTo Erro
        Do While contador < 1001
            'Captura as coordenadas do ponto de inserção do nó(bloco)
            With ThisDrawing.Utility
                .GetEntity objEnt01, varPick01, vbCr & "Selecione o nó: "
                'Define o objeto como bloco
                Set objBRef01 = objEnt01
                'Verifica se o bloco é um nó pelo TAG do atributo NOD_2D
                For Each AtrValor In objBRef01.GetAttributes
                    If AtrValor.TagString <> "NOD_2D" Then
                        MsgBox "Esta entidade não é um nó", vbApplicationModal + vbCritical, "Aviso"
                        Exit Do
                    End If
                Next AtrValor
            End With
            
            'Obtém as coordenadas do nó (bloco nó) selecionado
            intPoints01 = objBRef01.InsertionPoint
            coor(0) = intPoints01(0): coor(1) = intPoints01(1): coor(2) = intPoints01(2)

            'Insere o bloco da força
            Set bl01 = ThisDrawing.ModelSpace.InsertBlock(coor, strNomeBloco, Escala, Escala, Escala, 0)
            'rever
            ThisDrawing.SetVariable "ORTHOMODE", 1
            angu = ThisDrawing.Utility.GetAngle(coor, "Indique a direção:")
            bl01.Rotate coor, angu
            
            'Acessa os atributos do objeto bloco (blk) associando a variável matriz (var)
            var = bl01.GetAttributes
            ' Define a variável (att) aos elemento da matriz (var)
            Set att(0) = var(0)
            att(0).Rotation = 0
            
            'Coleta o número do nó
            For Each AtrValor In objBRef01.GetAttributes
                nomeNo = AtrValor.TextString
            Next AtrValor
                       
            'Registra o número do nó sujeito a força
            For Each var In bl01.GetAttributes
                If var.TagString = "INF_NO_2D" Then
                    var.TextString = nomeNo
                End If
            Next var
            
            'Adiciona 1 ao contador
            contador = contador + 1
        Loop
    Else
    End If
End If

Erro:
If bl01 Is Nothing Then
    ThisDrawing.Utility.Prompt "Rotina finalizada"
    ThisDrawing.SetVariable "osmode", osn
    'rever
    ThisDrawing.SetVariable "ORTHOMODE", 0
Else
End If

'Retorna a caixa de diálogo
TR2D.show

End Sub

Private Sub CommandButton6_Click()

'Declaração de variáveis
Dim coor(0 To 2) As Double
Dim bl01 As AcadBlockReference
Dim Escala As Integer
Dim osn As Integer
Dim a As Integer
Dim objBloco As AcadBlock
Dim strNomeBloco As String
Dim var As Variant
Dim att(0 To 20) As AcadAttributeReference
Dim AtrValor As Variant
Dim pto As Variant
Dim verfBloco As Boolean
Dim contador As Integer
Dim angu As Double
Dim objEnt01 As AcadEntity

'Ocultar a caixa de dialogo
TR2D.Hide
On Error Resume Next
'Inicia a variável de verificação da existencia do bloco do nó
verfBloco = False
'Inicia a variável contador
contador = 1

Escala = ThisDrawing.GetVariable("useri1") 'Variável que recebe o valor decimal da escala
ThisDrawing.SetVariable "useri1", Escala

'Condicional que verifica se a escala não foi definida e, portanto, tem o valor nulo (zero)
If Escala = 0 Then
    MsgBox "Escala não definida ", vbApplicationModal + vbCritical, "Aviso"
Else
    'Verifica se o bloco existe no desenho
    strNomeBloco = "AP_MV_2D"
    For Each objBloco In ThisDrawing.Blocks
        If 0 = StrComp(objBloco.Name, strNomeBloco, vbTextCompare) Then
            verfBloco = True
        End If
    Next objBloco
    
    If verfBloco = False Then
        'Caixa de mensagem informando a falta do bloco no desenho
        MsgBox "O bloco '" & strNomeBloco & "' não existe em seu desenho.", vbApplicationModal + vbCritical, "Aviso"
    ElseIf verfBloco = True Then
        'Muda o osmode para a configuração 9
        osn = ThisDrawing.GetVariable("osmode")
        ThisDrawing.SetVariable "osmode", 9
        
        On Error GoTo Erro
        Do While contador < 1001
            'Captura as coordenadas do ponto de inserção do nó(bloco)
            With ThisDrawing.Utility
                .GetEntity objEnt01, varPick01, vbCr & "Selecione o nó: "
                'Define o objeto como bloco
                Set objBRef01 = objEnt01
                'Verifica se o bloco é um nó pelo TAG do atributo NOD_2D
                For Each AtrValor In objBRef01.GetAttributes
                    If AtrValor.TagString <> "NOD_2D" Then
                        MsgBox "Esta entidade não é um nó", vbApplicationModal + vbCritical, "Aviso"
                        Exit Do
                    End If
                Next AtrValor
            End With
            
            'Obtém as coordenadas do nó (bloco nó) selecionado
            intPoints01 = objBRef01.InsertionPoint
            coor(0) = intPoints01(0): coor(1) = intPoints01(1): coor(2) = intPoints01(2)

            'Insere o bloco da força
            Set bl01 = ThisDrawing.ModelSpace.InsertBlock(coor, strNomeBloco, Escala, Escala, Escala, 0)
            'rever
            ThisDrawing.SetVariable "ORTHOMODE", 1
            angu = ThisDrawing.Utility.GetAngle(coor, "Indique a direção:")
            bl01.Rotate coor, angu
            
            'Acessa os atributos do objeto bloco (blk) associando a variável matriz (var)
            var = bl01.GetAttributes
            ' Define a variável (att) aos elemento da matriz (var)
            Set att(0) = var(0)
            att(0).Rotation = 0
            
            'Coleta o número do nó
            For Each AtrValor In objBRef01.GetAttributes
                nomeNo = AtrValor.TextString
            Next AtrValor
                       
            'Registra o número do nó sujeito a força
            For Each var In bl01.GetAttributes
                If var.TagString = "INF_NO_2D" Then
                    var.TextString = nomeNo
                End If
            Next var
            
            'Adiciona 1 ao contador
            contador = contador + 1
        Loop
    Else
    End If
End If
On Error GoTo 0
Exit Sub
Erro:
If bl01 Is Nothing Then
    ThisDrawing.Utility.Prompt "Rotina finalizada"
    ThisDrawing.SetVariable "osmode", osn
    'rever
    ThisDrawing.SetVariable "ORTHOMODE", 0
Else
End If

'Retorna a cai8xa de diálogo
TR2D.show
On Error GoTo 0
End Sub

Private Sub TRATRBPROP_Click()
Dim selSet As AcadSelectionSet
Dim ponto1 As Variant, ponto2 As Variant
'ThisDrawing.SelectionSets.Item("MySelectionSet").Delete
TR2D.Hide
'Cria um novo AcadSelectionSet e adiciona todos os objetos selecionados pelo usuário
Set selSet = ThisDrawing.SelectionSets.Add("MySelectionSet")
On Error GoTo Erro
With ThisDrawing.Utility
    .InitializeUserInput 1
    ponto1 = .GetPoint(, "Click no primeiro ponto")
    ponto2 = .GetCorner(ponto1, "Click no segundo ponto oposto")
    selSet.Select SelectionMode, ponto1, ponto2
    selSet.Highlight True
    selSet.Update
    .GetString False, "Pressione enter para aplicar as propriedades e finalizar"
End With

''''''''''''''''''''''''''''''''''''''''''''''''''''''''''''''''''''''''''''''''''''''''
'Define as variáveis necessárias
Dim objEnt01 As Object

Dim blk As AcadBlockReference
Dim att As Variant
Dim nomeBloco As String
Dim textoValMAT As String
Dim textoValSEC As String
Dim valorMAT As Double
Dim valorSEC As Double
Dim X As Integer
'ThisDrawing.SelectionSets.Item("MySelectionSet").Delete
textoValMAT = TextBox1.Value
If InStr(textoValMAT, ",") > 0 Then
    textoValMAT = Replace(TextBox1.Value, ",", ".")
Else
End If

textoValSEC = TextBox2.Value
If InStr(textoValSEC, ",") > 0 Then
    textoValSEC = Replace(textoValSEC, ",", ".")
Else
End If

'Percorre todos os blocos selecionados
For Each objEnt01 In selSet
    If StrComp(objEnt01.EntityName, "AcDbBlockReference", 1) = 0 Then
        nomeBloco = objEnt01.Name
        'Verifica se o nome do bloco é "ELEM_BAR_2D"
        If nomeBloco = "ELEM_BAR_2D" Then
            Set blk = objEnt01
            For Each att In blk.GetAttributes
                'Verifica se o atributo é do tipo "BAR_2D"
                If att.TagString = "MAT" Then
                'Preenche o valor do atributo com o obtido da caixa de texto de materiais
                    att.TextString = textoValMAT
                ElseIf att.TagString = "SEC" Then
                    att.TextString = textoValSEC
                End If
            Next att
        End If

    End If
    
Next objEnt01

'''''''''''''''''''''''''''''''''''''''''''''''''''''''''''''''''''''''''''''''''''''''''
selSet.Highlight False
selSet.Update
'Remove o AcadSelectionSet criado
ThisDrawing.SelectionSets.Item("MySelectionSet").Delete
ThisDrawing.Regen acAllViewports
TR2D.show

Erro:
    ThisDrawing.Regen acAllViewports
    TR2D.show
End Sub

Private Sub Fechar_TD2D_Click()
frm_decideFechar.show
End Sub

Private Sub abrirProp_Click()

frm_propriedades.show

'works = "D:\Projetos_Prog\ISRAG_RX1.exe"
'Shell (works)
'Call Shell("D:\Projetos_Prog\ISRAG_RX1.exe", vbNormalFocus)
End Sub
Private Sub Escala_Click()
frm_defesc.show
End Sub
Private Sub Label4_Click()

End Sub

Private Sub ListBox1_Click()

End Sub

Private Sub MultiPage1_Change()

End Sub

Private Sub Unidade_Click()
frm_deunit.show
End Sub

Private Sub UserForm_Initialize()


End Sub

Private Sub UserForm_QueryClose(Cancel As Integer, CloseMode As Integer)
If Fechar = False Then
    MsgBox "Para fechar a aplicação, por favor clique no botão Fechar! ", vbApplicationModal + vbCritical, "Aviso"
    Cancel = True
End If
End Sub

Attribute VB_Name = "frm_decideFechar"
Attribute VB_Base = "0{F76D0652-4DF8-49A8-95FB-8F89EF25B054}{75376578-76C9-42DD-9B8A-935204C4540A}"
Attribute VB_GlobalNameSpace = False
Attribute VB_Creatable = False
Attribute VB_PredeclaredId = True
Attribute VB_Exposed = False
Attribute VB_TemplateDerived = False
Attribute VB_Customizable = False
Private Sub NaoFechar_Click()
frm_decideFechar.Hide
End Sub

Private Sub SimFechar_Click()
End
End Sub


Private Sub UserForm_Click()

End Sub

Attribute VB_Name = "frm_defesc"
Attribute VB_Base = "0{9BE2EC62-74F1-4969-B8F8-CDCA84986ED2}{0723EBED-23A0-4DBB-8291-CEF903529BE7}"
Attribute VB_GlobalNameSpace = False
Attribute VB_Creatable = False
Attribute VB_PredeclaredId = True
Attribute VB_Exposed = False
Attribute VB_TemplateDerived = False
Attribute VB_Customizable = False
Private Sub cmd_altesc_Click()
'Programa criado por Hélio Guerrini - 30/12/2022

Dim esc As Double 'Declaração da variável que recebe o valor da escala do modelo

'Variável que recebe o valor da escala do modelo
esc = TextBox1.Value
If InStr(textoValMAT, ",") > 0 Then
    esc = Replace(TextBox1.Value, ",", ".")
Else
End If

If esc > 0 Then
    ThisDrawing.SetVariable "useri1", esc
    MsgBox "O novo fator de escala do desenho é " & esc, vbApplicationModal + vbInformation, "Aviso"
Else
    MsgBox "Por favor use apenas valores maiores que zero", vbApplicationModal + vbCritical, "Aviso"
End If

End Sub

Private Sub CommandButton1_Click()
If ThisDrawing.GetVariable("useri1") <= 0 Then
    MsgBox "O fator de escala não foi indicado", vbApplicationModal + vbCritical, "Aviso"
End If
Unload frm_defesc
End Sub

Private Sub TextBox1_Change()

End Sub

Private Sub TextBox1_KeyPress(ByVal KeyAscii As MSForms.ReturnInteger)
    Dim CaracterePermitido As Boolean
    CaracterePermitido = False 'Inicializa a variável como falsa
    
    'Verifica se o caractere digitado é numérico ou a letra "e"
    If IsNumeric(Chr(KeyAscii)) Or Chr(KeyAscii) = "e" Then
        CaracterePermitido = True 'Marca a variável como verdadeira
    End If
    
    'Cancela a tecla digitada se o caractere não for permitido
    If Not CaracterePermitido And KeyAscii <> 8 Then
        KeyAscii = 0
    End If
End Sub

Private Sub UserForm_Click()

End Sub

Attribute VB_Name = "frm_deunit"
Attribute VB_Base = "0{D212DB46-3E9D-4F61-958E-59B3899159C4}{70E1F554-84C6-4F2B-8701-E825E9F40D29}"
Attribute VB_GlobalNameSpace = False
Attribute VB_Creatable = False
Attribute VB_PredeclaredId = True
Attribute VB_Exposed = False
Attribute VB_TemplateDerived = False
Attribute VB_Customizable = False
Private Sub ComboComp_Change()
 
End Sub

Private Sub CommandButton1_Click()
Unload frm_deunit

End Sub

Private Sub DefineUnit_Click()
Dim vetorCompUnit() As Variant
Dim vetorForcaUnit() As Variant

vetorCompUnit = Array("Unitless", "Polegadas in", "Pés ft", "Milhas", "Milímetros - mm", "Centímetros - cm", _
"Metros - m", "Quilômetros - km", "Micropolegadas", "Mils", "Jardas - yd", "Angstrom", "Nanômetros", "Microns", _
"Decímetros - dm", "Decâmetros - dam", "Hectômetro - hm", "Gigametros - Gm", "Unidade astronômica - AU", "Ano-luz", "Parsecs")

vetorForcaUnit = Array("Newton (N)", "Quilograma-força (kgf)", "Grama-força (gf)", "Libra-força (lbf)")

If ComboComp.ListIndex = -1 Then
    MsgBox "Unidade de comprimento não selecionada"
Else
    ThisDrawing.SetVariable "insunits", ComboComp.ListIndex
    Me.MostrarUnid.Caption = vetorCompUnit(ComboComp.ListIndex)
End If

If ComboForca.ListIndex = -1 Then
    MsgBox "Unidade de força não selecionada"
Else
    ThisDrawing.SetVariable "useri2", ComboForca.ListIndex
    Me.MostraUnidForca.Caption = vetorForcaUnit(ComboForca.ListIndex)
End If



End Sub

Private Sub MostrarUnid_Click()

End Sub

Private Sub UserForm_Click()



End Sub

Private Sub UserForm_Initialize()
'INSUNITS
'Unitless = 0
'Inches (in) = 1
'Feet (ft) = 2
'Miles = 3
'Milímetros = 4
'Centímetros = 5
'Metros = 6
'Quilômetros = 7
'Micropolegadas = 8
'Mils = 9
'Jardas = 10
'Angstrom = 11
'Nanômetros = 12
'Microns = 13
'Decímetros = 14
'Decâmetros = 15
'Hectômetro = 16
'Gigametros = 17
'Unidade astronômica = 18
'Ano-luz = 19
'Parsecs = 20

Dim UnidadeCorr As Integer
Dim vetorCompUnit() As Variant
Dim vetorForcaUnit() As Variant

UnidadeCorr = ThisDrawing.GetVariable("insunits")

vetorCompUnit = Array("Unitless", "Polegadas in", "Pés ft", "Milhas", "Milímetros - mm", "Centímetros - cm", _
"Metros - m", "Quilômetros - km", "Micropolegadas", "Mils", "Jardas - yd", "Angstrom", "Nanômetros", "Microns", _
"Decímetros - dm", "Decâmetros - dam", "Hectômetro - hm", "Gigametros - Gm", "Unidade astronômica - AU", "Ano-luz", "Parsecs")

Me.MostrarUnid.Caption = vetorCompUnit(UnidadeCorr)

UnidadeCorr = ThisDrawing.GetVariable("useri2")

vetorForcaUnit = Array("Newton (N)", "Quilograma-força (kgf)", "Grama-força (gf)", "Libra-força (lbf)")

Me.MostraUnidForca.Caption = vetorForcaUnit(UnidadeCorr)

With ComboComp
    .AddItem "Unitless"
    .AddItem "Inches (polegadas in)"
    .AddItem "Feet (pés ft)"
    .AddItem "Miles (milhas)"
    .AddItem "Milímetros (mm)"
    .AddItem "Centímetros (cm)"
    .AddItem "Metros (m)"
    .AddItem "Quilômetros (km)"
    .AddItem "Micropolegadas (micro-in)"
    .AddItem "Mils (mil)"
    .AddItem "Jardas (yd)"
    .AddItem "Angstrom"
    .AddItem "Nanômetros"
    .AddItem "Microns"
    .AddItem "Decímetros (dm)"
    .AddItem "Decâmetros (dam)"
    .AddItem "Hectômetro (hm)"
    .AddItem "Gigametros (Gm)"
    .AddItem "Unidade astronômica (AU)"
    .AddItem "Ano-luz"
    .AddItem "Parsecs"
    
End With

With ComboForca
    .AddItem "Newton (N)"
    .AddItem "Quilograma-força (kgf)"
    .AddItem "Grama-força (gf)"
    .AddItem "Libra-força (lbf)"
End With


End Sub
